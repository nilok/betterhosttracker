module host-tracker-service {
    namespace "urn:opendaylight:betterhosttracker";
    prefix host-track;

    import yang-ext {prefix ext;}
    import ietf-inet-types {prefix inet;}
    import ietf-yang-types {prefix yang;}
    import opendaylight-inventory {prefix inv;}
    import opendaylight-l2-types {prefix l2t;}
    import address-tracker {prefix at;}

    revision 2014-06-24 {
        description
            "draft based on address-tracker 2014-06-17";
    }

    typedef host-id {
        type yang:uuid;
    }

    grouping host {
        uses at:address-node-connector;
        leaf id {
            type host-id;
            description "unique host identifier";
        }
    }
}
